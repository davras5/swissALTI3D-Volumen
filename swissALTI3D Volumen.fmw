FME workspace swissALTI3D Volumen.fmw

Note: Input Point
Creator
    GEOM = <?xml version="1.0" encoding="US_ASCII" standalone="no" ?><geometry><point><coord x="8.939944" y="46.006074"/></point></geometry>
    GEOMTYPE = Geometry Object
    NUM = 1
    CREATED -> CoordinateSystemSetter
Note: WGS 84
CoordinateSystemSetter
    COORDSYS = LL-WGS84
    -> Reprojector
Note: To LV95
Reprojector
    DEST = CH1903Plus_1.LV95/01
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> CoordinateExtractor
    REPROJECTED -> FeatureReader_2 [INITIATOR]
Note: GeoTiff / Höhenmodell / swissSURFACE3D Raster
FeatureReader_2
    ATTRIBUTES = GEOTIFF,
    ATTR_ACCUM_MODE = Only Use Result
    CLIP_TO_ENVELOPE = NO
    COMBINE_GEOM = Use Result
    DATASET = C:\Users\DavidRasner\Downloads\swisssurface3d-raster_2020_2716-1096_0.5_2056_5728.tif
    FORMAT = GEOTIFF
    GEOMETRY_TYPES = GEOTIFF,""",fme_raster"""
    GEOTIFF_APPLY_GCPS = NO
    GEOTIFF_FEATURE_TYPE_NAME = FORMAT_NAME
    GEOTIFF_IGNORE_RASTER_TYPE_KEY = No
    GEOTIFF_LENIENT_READ = Yes
    GEOTIFF_NATIVELY_HANDLED_WEBSERVICES = s3connector,azurestorage,google-cloud-storage
    GEOTIFF_PREFER_FILE_CS_UNITS = Yes
    GEOTIFF_READER_META_ATTRIBUTES = fme_dataset fme_basename
    GEOTIFF_READ_OFFSETS_IN_CS_UNITS = No
    GEOTIFF_SCALE_COLOR_TO_STANDARD_BIT_DEPTH = YES
    GEOTIFF_USE_SEARCH_ENVELOPE = NO
    INITIATOR_FIRST_OUTPUT = default
    INTERACT = NONE
    ORDER_RESULTS = No
    OUTPUT_ADD_SCHEMA_ATTRIBUTES = NO
    OUTPUT_FEATURES_DISPLAY = Schema and Data Features
    GEOTIFF -> PointOnRasterValueExtractor [RASTER]
CoordinateExtractor
    LIST_NAME = _indices
    RECURSIVE = Yes
    MODE = All Coordinates
    -> HTTPCaller
Note: Swisstopo Elevation
HTTPCaller
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api3.geo.admin.ch/rest/services/height?easting=@Value(_indices{0}.x)&northing=@Value(_indices{0}.y)&sr=2056
    TRANSFER_TIMEOUT_LENGTH = 90
    USE_COOKIES = No
    VERIFY_SSL_CERTIFICATES = Yes
    -> JSONExtractor
JSONExtractor
    EXTRACT_QUERY_TABLE = ele_base json["height"]
    JSON_DOCUMENT = @Value(_response_body)
    READ_FROM_FILE = NO
    EVALUATED -> FeatureReader [INITIATOR]
Note: Amtliche Vermessung
FeatureReader
    ATTRIBUTES = cppt,"BFSNr,Kategorie,Nummer,Koordinate,Hoehe,Punktzeichen,Begehbar,Kanton,fid",dprsf,"BFSNr,NBIdent,Nummer,EGRIS_EGRID,Vollstaendigkeit,Art,Flaeche,Gueltigkeit,Kanton,fid",dprsfproj,"BFSNr,NBIdent,Nummer,EGRIS_EGRID,Vollstaendigkeit,Art,Flaeche,Kanton,fid",hadr,"BFSNr,Hausnummer,Gebaeudename,GWR_EGID,GWR_EDID,Strassenname,PLZ,Zusatzziffern,Ortschaftsname,Ori,Loc,Kanton,fid",lcobj,"BFSNr,Typ,Text,Art,Ori,Loc,Kanton,fid",lcsf,"BFSNr,Qualitaet,Art,GWR_EGID,Kanton,fid",lcsfproj,"BFSNr,Qualitaet,Art,GWR_EGID,Kanton,fid",lnna,"BFSNr,Kategorie,Name,Ori,Loc,Kanton,fid",locpos,"BFSNr,Strassenname,Ori,Loc,Kanton,fid",mbsf,"BFSNr,Name,Kanton,fid",osbp,"BFSNr,Gueltigkeit,Punktzeichen,Kanton,fid",osnr,"BFSNr,NBIdent,Nummer,Ori,Loc,Dif,Kanton,fid",osnrproj,"BFSNr,NBIdent,Nummer,Ori,Loc,Dif,Kanton,fid",plli,"BFSNr,Betreiber,Medium,Gueltigkeit,Sichtbarkeit,Kanton,fid",plna,"BFSNr,Betreiber,Ori,Loc,Kanton,fid",plsf,"BFSNr,Betreiber,Medium,Gueltigkeit,Kanton,fid",resf,"BFSNr,NBIdent,Nummer,EGRIS_EGRID,Vollstaendigkeit,Flaeche,Gueltigkeit,Kanton,fid",resfhl,"BFSNr,Kanton,fid",resfproj,"BFSNr,NBIdent,Nummer,EGRIS_EGRID,Vollstaendigkeit,Flaeche,Kanton,fid",slide,"BFSNr,NBIdent,Identifikator,Name,Gueltiger_Eintrag,Kanton,fid",slideobj,"BFSNr,NBIdent,Identifikator,Name,Ori,Loc,Kanton,fid",soli,"BFSNr,Gueltigkeit,Art,Qualitaet,Kanton,fid",soobj,"BFSNr,Typ,Text,Art,Ori,Loc,Kanton,fid",sopt,"BFSNr,Gueltigkeit,Art,Qualitaet,Ori,Kanton,fid",sosf,"BFSNr,Gueltigkeit,Art,Qualitaet,GWR_EGID,Kanton,fid",tbbp,"BFSNr,Gueltigkeit,Punktzeichen,Hoheitsgrenzpunkt,Kanton,fid",tbli,"Typ,Gueltigkeit,Kanton,fid"
    ATTR_ACCUM_MODE = Merge Initiator and Result
    ATTR_CONFLICT_RES = Use Result
    ATTR_IGNORE_NULLS = No
    COMBINE_GEOM = Use Result
    DATASET = C:\Users\DavidRasner\Downloads\av_lv95\geopackage\av_2056.gpkg
    FEATURETYPES = lcsf
    FORMAT = OGCGEOPACKAGE
    GEOMETRY_TYPES = cppt,"""wkb_geometry,fme_point""",dprsf,"""wkb_geometry,fme_arc,fme_area,fme_collection,fme_line,fme_point,fme_solid""",dprsfproj,"""wkb_geometry,fme_area""",hadr,"""wkb_geometry,fme_point""",lcobj,"""wkb_geometry,fme_point""",lcsf,"""wkb_geometry,fme_arc,fme_area,fme_collection,fme_line,fme_point,fme_solid""",lcsfproj,"""wkb_geometry,fme_arc,fme_area,fme_collection,fme_line,fme_point,fme_solid""",lnna,"""wkb_geometry,fme_point""",locpos,"""wkb_geometry,fme_point""",mbsf,"""wkb_geometry,fme_area""",osbp,"""wkb_geometry,fme_point""",osnr,"""wkb_geometry,fme_point""",osnrproj,"""wkb_geometry,fme_point""",plli,"""wkb_geometry,fme_line""",plna,"""wkb_geometry,fme_point""",plsf,"""wkb_geometry,fme_area""",resf,"""wkb_geometry,fme_arc,fme_area,fme_collection,fme_line,fme_point,fme_solid""",resfhl,"""wkb_geometry,fme_line""",resfproj,"""wkb_geometry,fme_arc,fme_area,fme_collection,fme_line,fme_point,fme_solid""",slide,"""wkb_geometry,fme_area""",slideobj,"""wkb_geometry,fme_point""",soli,"""wkb_geometry,fme_line""",soobj,"""wkb_geometry,fme_point""",sopt,"""wkb_geometry,fme_point""",sosf,"""wkb_geometry,fme_arc,fme_area,fme_collection,fme_line,fme_point,fme_solid""",tbbp,"""wkb_geometry,fme_point""",tbli,"""wkb_geometry,fme_line"""
    INITIATOR_FIRST_OUTPUT = default
    INTERACT = WITHIN
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = Art="Gebaeude"
    lcsf -> GeographicAreaCalculator
Note: Calculate / Gebäudegrundfläche GGF
GeographicAreaCalculator
    AREA_ATTR = _area
    AreaMult = 1
    -> BoundingBoxReplacer
    -> SpatialFilter [Filter]
Note: Oriented / _rotation
BoundingBoxReplacer
    BBANGLE = _rotation
    BBTYPE = MINBB
    BOXTYPE = 2D Oriented Bounding Box
    BOX -> BoundingBoxReplacer_2
BoundingBoxReplacer_2
    BBTYPE = BB
    BOXTYPE = 2D Bounding Box
    BOX -> CenterPointExtractor
CenterPointExtractor
    CENTX = _inside_x
    CENTY = _inside_y
    CENTZ = _inside_z
    EXTRACTIONMODE = CENTER
    -> 2DGridAccumulator
    -> FeatureMerger [SUPPLIER]
Note: 1x1 Grid
2DGridAccumulator
    BBOX_TYPE = GRID_POLYGONS
    COL_ATTR = _column
    GRID_ORIGIN = BOTTOM_LEFT
    ROW_ATTR = _row
    SIZE_TYPE = Cell Size
    XINC = 1
    YINC = 1
    GRID_TYPE = Polygons
    STARTINGCORNER = Lower Left
    GRID -> FeatureMerger [REQUESTOR]
FeatureMerger
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Rotator_2
Rotator_2
    ANGLE = @Value(_rotation)
    XORIG = @Value(_inside_x)
    YORIG = @Value(_inside_y)
    ROTATED -> SpatialFilter [Candidate]
SpatialFilter
    AGGREGATE_HANDLING = Yes
    ATTR_ACCUM_MODE = Merge Filter
    ATTR_CONFLICT_RES = Use Candidate
    BASE_TYPE = Single Filter
    CURVE_BOUNDARY_RULE_PARAM = Default Rule
    PASS_CRITERIA = Pass Against One Filter
    PREDATTR = _predicate
    PREDICATES = CONTAINS
    USE_BOUNDING_BOX = No
    PASSED -> GeometryExtractor
GeometryExtractor
    ATTR = _geometry
    KIND = fmebinary
    REMOVE_GEOMETRY = No
    KIND_LONG = FME Binary
    -> CenterPointReplacer
CenterPointReplacer
    POINTTYPE = CENTER
    POINT -> PointOnRasterValueExtractor [POINT]
PointOnRasterValueExtractor
    INTERPOLATION_TYPE = NearestNeighbor
    INTERPOLATION_TYPE_NAME = Nearest Neighbor
    POINT -> AttributeCreator
Note: ele_roof
AttributeCreator
    ATTR_TABLE = SET_TO ele_roof (varchar(200)) = @Value(_band{0}.value)
    -> GeometryReplacer
GeometryReplacer
    KIND = fmebinary
    REMOVE_ATTRIBUTE = Yes
    SOURCE = @Value(_geometry)
    KIND_LONG = FME Binary
    -> Extruder
Extruder
    DIRECTION_LOOKUP = AUTO
    DISTANCE = @Value(ele_roof)-@Value(ele_base)
    DIRECTION = Auto
    EXTRUDED -> FeatureWriter [Extruded]
    EXTRUDED -> VolumeCalculator
VolumeCalculator
    MULT = 1
    SET_TRAIT = No
    VOLUME_ATTR = _volume
    -> Aggregator
Aggregator
    ACCUM_ATTRS = None
    AGGREGATE_TYPE = Homogeneous Collection (If Possible)
    MODE = Geometry - Assemble One Level
    SEP = ,
    SUM = _volume
FeatureWriter
    DATASET = C:\Users\DavidRasner\Desktop
    DATASET_ATTR = _dataset
    FEATURE_TYPE_LIST_ATTR = _feature_types
    FORMAT = STL
    STL_DESTINATION_DATASETTYPE_VALIDATION = Yes
    STL_FILE_TYPE = BINARY
    STL_LOCAL_COORDSYS_TRANSFORMATION = OFFSET_CENTROID_TO_ORIGIN
    STL_MOVE_TO_LOCAL_COORDSYS = No
    TOTAL_FEATURES_WRITTEN_ATTR = _total_features_written
